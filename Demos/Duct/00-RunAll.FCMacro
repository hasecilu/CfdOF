from os import path
from CfdOF.CfdTools import executeMacro
dir = path.dirname(__file__)
executeMacro(path.join(dir, '01-geom.FCMacro'))
executeMacro(path.join(dir, '02-mesh.FCMacro'))
executeMacro(path.join(dir, '03-porous.FCMacro'))
executeMacro(path.join(dir, '04-screen.FCMacro'))
